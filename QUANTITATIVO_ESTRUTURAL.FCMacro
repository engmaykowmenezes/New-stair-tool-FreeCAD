lista = App.ActiveDocument.Objects

pilares = []
vigas = []
lajes = []

#renomeia as vigas e os pilares e as coloca em listas diferentes
for obj in lista:
    
    try:
        print(obj.IfcType)
        if obj.IfcType == 'Column':
            pilares.append(obj)
            obj.Label = 'P'+str(len(pilares))

        elif obj.IfcType == 'Beam':
            vigas.append(obj)
            obj.Label = 'V'+str(len(vigas))

        elif obj.IfcType == 'Slab':
            lajes.append(obj)
            obj.Label = 'L'+str(len(lajes))

        else:
            pass  
    except:
        pass

#TABELA ESTRUTURA
tabela = App.activeDocument().addObject('Spreadsheet::Sheet','Estrutura')

if len(pilares) > 0:
    #PILARES###############################################################
    tabela.mergeCells('A1:E1')#Uni as celulas da tabela
    tabela.setAlignment('A1:E1', 'center', 'keep')#Centraliza o texto
    tabela.set('A1','PILARES')
    tabela.setBackground('A1',(0.000000,0.501961,0.000000))
    tabela.setForeground('A1', (1.000000,1.000000,1.000000))

    tabela.set('A2','Ref.')
    tabela.set('B2','Altura')
    tabela.set('C2','Comprimento')
    tabela.set('D2','Largura')
    tabela.set('E2','Volume')
    tabela.setBackground('A2:E2', (0.752941,0.752941,0.752941))

     
    for i in range(3,len(pilares)+3):
        tabela.set('A'+str(i),str(pilares[i-3].Label))
        tabela.set('B'+str(i),'=<<'+str(pilares[i-3].Label)+'>>.Height')
        tabela.set('C'+str(i),'=<<'+str(pilares[i-3].Label)+'>>.Length')
        tabela.set('D'+str(i),'=<<'+str(pilares[i-3].Label)+'>>.Width')

        tabela.set('E'+str(i),'=B'+str(i)+'*'+'C'+str(i)+'*''D'+str(i))
        tabela.setDisplayUnit('E'+str(i), 'm^3')

    equacao = '='
    for i in range(3,len(pilares)+3):
        equacao+='+E'+str(i)
    tabela.set('D'+str(len(pilares)+3),'Total:')
    tabela.set('E'+str(len(pilares)+3),equacao)
    tabela.setDisplayUnit('E'+str(len(pilares)+3), 'm^3')



if len(vigas) > 0:
    #VIGAS############################################################
    tabela.mergeCells('G1:K1')#Uni as celulas da tabela
    tabela.setAlignment('G1:K1', 'center', 'keep')#Centraliza o texto
    tabela.set('G1','VIGAS')
    tabela.setBackground('G1',(0.000000,0.501961,0.000000))
    tabela.setForeground('G1', (1.000000,1.000000,1.000000))

    tabela.set('G2','Ref.')
    tabela.set('H2','Altura')
    tabela.set('I2','Comprimento')
    tabela.set('J2','Largura')
    tabela.set('K2','Volume')
    tabela.setBackground('G2:K2', (0.752941,0.752941,0.752941))

     
    for i in range(3,len(vigas)+3):
        tabela.set('G'+str(i),str(vigas[i-3].Label))
        tabela.set('H'+str(i),'=<<'+str(vigas[i-3].Label)+'>>.Height')
        tabela.set('I'+str(i),'=<<'+str(vigas[i-3].Label)+'>>.Length')
        tabela.set('J'+str(i),'=<<'+str(vigas[i-3].Label)+'>>.Width')

        tabela.set('K'+str(i),'=H'+str(i)+'*'+'I'+str(i)+'*''J'+str(i))
        tabela.setDisplayUnit('K'+str(i), 'm^3')

    equacao = '='
    for i in range(3,len(vigas)+3):
        equacao+='+K'+str(i)
    tabela.set('J'+str(len(vigas)+3),'Total:')
    tabela.set('K'+str(len(vigas)+3),equacao)
    tabela.setDisplayUnit('K'+str(len(vigas)+3), 'm^3')

if len(lajes) > 0:
    #LAJES############################################################
    tabela.mergeCells('M1:P1')#Uni as celulas da tabela
    tabela.setAlignment('M1:P1', 'center', 'keep')#Centraliza o texto
    tabela.set('M1','Lajes')
    tabela.setBackground('M1',(0.000000,0.501961,0.000000))
    tabela.setForeground('M1', (1.000000,1.000000,1.000000))

    tabela.set('M2','Ref.')
    tabela.set('N2','Área')
    tabela.set('O2','Altura')
    tabela.set('P2','Volume')
    tabela.setBackground('M2:P2', (0.752941,0.752941,0.752941))

     
    for i in range(3,len(lajes)+3):
        tabela.set('M'+str(i),str(lajes[i-3].Label))
        tabela.set('N'+str(i),'=<<'+str(lajes[i-3].Label)+'>>.HorizontalArea')
        tabela.set('O'+str(i),'=<<'+str(lajes[i-3].Label)+'>>.Height')

        tabela.set('P'+str(i),'=N'+str(i)+'*'+'O'+str(i))
        tabela.setDisplayUnit('P'+str(i), 'm^3')

    equacao = '='
    equacao2 = '='
    for i in range(3,len(lajes)+3):
        equacao+='+P'+str(i)
        equacao2+= '+N'+str(i)

    tabela.set('M'+str(len(lajes)+3),'Total:')
    tabela.set('P'+str(len(lajes)+3),equacao)
    tabela.set('N'+str(len(lajes)+3),equacao2)
    tabela.setDisplayUnit('K'+str(len(lajes)+3), 'm^3')


    App.ActiveDocument.recompute()
