#Macro FreeCAD dedicada a modelagem paramétrica de escada circular
#Autor: Eng. Maykow Menezes; +55(62)993990525; eng.maykowmenezes@gmail.com



from tkinter import *
import math
import Draft
import Arch

#Gui.activateWorkbench("BIMWorkbench")

class Escada():
	def __init__(self,root):
		self.doc = App.ActiveDocument

		self.espelho = 20
		self.piso = 0

		self.Lab_altura = Label(root,text = 'Altura (cm):')
		self.Lab_altura.grid( row = 0, column = 0,  sticky = 'w')
		self.altura = Entry(root,width = 5)
		self.altura.grid( row = 0, column = 1, sticky = 'e', padx = 20, pady = 5)

		self.Lab_largura = Label(root,text = 'Largura (cm):')
		self.Lab_largura.grid( row = 1, column = 0, sticky = 'w')
		self.largura = Entry(root,width = 5)
		self.largura.grid(row = 1, column =1, sticky = 'e',padx = 20, pady = 5)


		self.Lab_degral = Label(root,text = 'Nº Degraus:')
		self.Lab_degral.grid( row = 2, column = 0, sticky = 'w')
		self.degral = Entry(root,width = 5)
		self.degral.grid(row = 2, column =1, sticky = 'e',padx = 20, pady = 5)

		self.Lab_especura = Label(root,text = 'Espessura (cm):')
		self.Lab_especura.grid( row = 3, column = 0, sticky = 'w')
		self.especura = Entry(root,width = 5)
		self.especura.grid(row = 3, column =1, sticky = 'e',padx = 20, pady = 5)

		self.Lab_calc = Label(root, text = '2E + P = 64')
		self.Lab_calc.grid(row = 4, column = 1,sticky = 'e')
		self.btn_calc = Button(root, text = 'Calcular', width = 6,command = self.calc)
		self.btn_calc.grid(row = 4, column = 0, padx = 20, pady = 5, sticky = 'w')

		self.Lab_espelho = Label(root,text = 'Espelho:')
		self.Lab_espelho.grid( row = 5, column = 0, sticky = 'w')
		self.Lab_espelho_resultado = Label(root,text = '')
		self.Lab_espelho_resultado.grid( row = 5, column = 1, sticky = 'w')


		self.Lab_piso = Label(root,text = 'Piso:')
		self.Lab_piso.grid( row = 6, column = 0, sticky = 'w')
		self.Lab_piso_resultado= Label(root,text = '')
		self.Lab_piso_resultado.grid( row = 6, column = 1, sticky = 'w')


		self.btn_modelar = Button(text = 'Modelar Escada', width = 20, command = self.modelar)
		self.btn_modelar.grid(row = 7, column = 0, columnspan = 2)

	def calc(self):
		self.espelho = float(self.altura.get())/float(self.degral.get())
		self.piso = 64-(2*self.espelho)

		self.Lab_espelho_resultado.configure(text = str(round(self.espelho,3))+ ' cm')
		self.Lab_piso_resultado.configure(text = str(round(self.piso,3))+ ' cm') 

	def modelar(self):
		self.calc()
		retangulos = []
		n_deg_ini = math.ceil((float(self.degral.get())-6)/2)
		n_deg_fin = math.floor((float(self.degral.get())-6)/2)

		for i in range(1,n_deg_ini+1):
			pl = FreeCAD.Placement()
			pl.Rotation.Q = (0.0,0.0,0.0,1.0)
			pl.Base = (0.0,i*self.piso*10,i*self.espelho*10)

			retangulos.append(Draft.makeRectangle(length=float(self.largura.get())*10, height= self.piso*10, placement=pl, face=True, support=None))
		
		for i in range(1,n_deg_fin+1):
			n = n_deg_ini + 6 + (i)

			pl = FreeCAD.Placement()
			pl.Rotation.Q = (0.0,0.0,0.0,1.0)
			pl.Base = (float(self.largura.get())*10,(self.piso*(n_deg_ini+1-i))*10,n*self.espelho*10)

			retangulos.append(Draft.makeRectangle(length=float(self.largura.get())*10, height= self.piso*10, placement=pl, face=True, support=None))

		#########curva###############################

		o = (float(self.largura.get())*10,((n_deg_ini+1)*self.piso)*10)
		a = (0,((n_deg_ini+1)*self.piso)*10)
		c = (0,a[1]+float(self.largura.get())*10)
		e = (o[0],c[1])
		g = (2*o[0],e[1])
		i = (g[0],a[1])
		b = (0,(a[1]+c[1])/2)
		d = ((a[0]+o[0])/2,c[1])
		f = ((o[0]+i[0])/2,c[1])
		h = (i[0], b[1])

		pl = FreeCAD.Placement()
		pl.Rotation.Q = (0.0,0.0,0.0,1.0)
		pl.Base = (0.0,0.0,0.0)

		n =1
		deg = [FreeCAD.Vector(o[0],o[1],(n_deg_ini+n)*self.espelho*10),FreeCAD.Vector(a[0],a[1],(n_deg_ini+n)*self.espelho*10),FreeCAD.Vector(b[0],b[1],(n_deg_ini+n)*self.espelho*10)]
		retangulos.append(Draft.makeWire(deg, placement=pl, closed=True, face=True, support=None))

		n = 2
		deg = [FreeCAD.Vector(o[0],o[1],(n_deg_ini+n)*self.espelho*10),FreeCAD.Vector(b[0],b[1],(n_deg_ini+n)*self.espelho*10),FreeCAD.Vector(c[0],c[1],(n_deg_ini+n)*self.espelho*10),FreeCAD.Vector(d[0],d[1],(n_deg_ini+n)*self.espelho*10)]
		retangulos.append(Draft.makeWire(deg, placement=pl, closed=True, face=True, support=None))

		n =3
		deg = [FreeCAD.Vector(o[0],o[1],(n_deg_ini+n)*self.espelho*10),FreeCAD.Vector(d[0],d[1],(n_deg_ini+n)*self.espelho*10),FreeCAD.Vector(e[0],e[1],(n_deg_ini+n)*self.espelho*10)]
		retangulos.append(Draft.makeWire(deg, placement=pl, closed=True, face=True, support=None))

		n =4
		deg = [FreeCAD.Vector(o[0],o[1],(n_deg_ini+n)*self.espelho*10),FreeCAD.Vector(e[0],e[1],(n_deg_ini+n)*self.espelho*10),FreeCAD.Vector(f[0],f[1],(n_deg_ini+n)*self.espelho*10)]
		retangulos.append(Draft.makeWire(deg, placement=pl, closed=True, face=True, support=None))

		n = 5
		deg = [FreeCAD.Vector(o[0],o[1],(n_deg_ini+n)*self.espelho*10),FreeCAD.Vector(f[0],f[1],(n_deg_ini+n)*self.espelho*10),FreeCAD.Vector(g[0],g[1],(n_deg_ini+n)*self.espelho*10),FreeCAD.Vector(h[0],h[1],(n_deg_ini+n)*self.espelho*10)]
		retangulos.append(Draft.makeWire(deg, placement=pl, closed=True, face=True, support=None))

		n =6
		deg = [FreeCAD.Vector(o[0],o[1],(n_deg_ini+n)*self.espelho*10),FreeCAD.Vector(h[0],h[1],(n_deg_ini+n)*self.espelho*10),FreeCAD.Vector(i[0],i[1],(n_deg_ini+n)*self.espelho*10)]
		retangulos.append(Draft.makeWire(deg, placement=pl, closed=True, face=True, support=None))
		
		degraus = []
		for i in retangulos:
			f = self.doc.addObject('Part::Extrusion','Extrude')
			f.Base = i
			f.DirMode = 'Normal'
			f.DirLink = None
			f.LengthFwd = 0.0
			f.LengthRev = float(self.especura.get())*10
			f.Solid = False
			f.Reversed = False
			f.Symmetric = False
			f.TaperAngle = 0.0
			f.TaperAngleRev = 0.0

			degraus.append(f)

		for i in retangulos: 
			i.Visibility = False

		fusao = self.doc.addObject("Part::MultiFuse","Fusion")
		fusao.Shapes = degraus

		for i in degraus:
			i.Visibility = False

		obj = Arch.makeStairs(baseobj=[fusao])
		fusao.Visibility = False


		
		root.destroy()	


root = Tk()
janela = Escada(root)
root.title("Escada Circular")
root.mainloop()
