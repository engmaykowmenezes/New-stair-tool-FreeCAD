#Macro FreeCAD dedicada a modelagem paramétrica de escada circular
#Autor: Eng. Maykow Menezes; +55(62)993990525; eng.maykowmenezes@gmail.com
# A macro depende do IfcType estar confugurado corretamente para cada tipo de objeto. é recomendado que cada os objetos sejam 


lista = App.ActiveDocument.Objects

pilares = []
vigas = []
lajes = []
paredes =[]
janelas = []
portas = []

tabelas = [] 

#renomeia as vigas e os pilares e as coloca em listas diferentes
for obj in lista:
    
    try:
        print(obj.IfcType)
        if obj.IfcType == 'Column':
            pilares.append(obj)
            obj.Label = 'P'+str(len(pilares))

        elif obj.IfcType == 'Beam':
            vigas.append(obj)
            obj.Label = 'V'+str(len(vigas))

        elif obj.IfcType == 'Slab':
            lajes.append(obj)
            obj.Label = 'L'+str(len(lajes))

        elif obj.IfcType == 'Wall':
            paredes.append(obj)
            obj.Label = 'Parede'+str(len(paredes))

        elif obj.IfcType == 'Window':
            janelas.append(obj)
            obj.Label = 'Janela'+str(len(janelas))

        else:

            pass  
    except:
        pass



if len(pilares) > 0:
    #TABELA PILARES
    tabela = App.activeDocument().addObject('Spreadsheet::Sheet','Pilares')
    tabelas.append(tabela)
    #PILARES###############################################################
    tabela.mergeCells('A1:E1')#Uni as celulas da tabela
    tabela.setAlignment('A1:E1', 'center', 'keep')#Centraliza o texto
    tabela.set('A1','PILARES')
    tabela.setBackground('A1',(0.000000,0.501961,0.000000))
    tabela.setForeground('A1', (1.000000,1.000000,1.000000))

    tabela.set('A2','Ref.')
    tabela.set('B2','Altura')
    tabela.set('C2','Comprimento')
    tabela.set('D2','Largura')
    tabela.set('E2','Volume')
    tabela.setBackground('A2:E2', (0.752941,0.752941,0.752941))

     
    for i in range(3,len(pilares)+3):
        tabela.set('A'+str(i),str(pilares[i-3].Label))
        tabela.set('B'+str(i),'=<<'+str(pilares[i-3].Label)+'>>.Height')
        tabela.set('C'+str(i),'=<<'+str(pilares[i-3].Label)+'>>.Length')
        tabela.set('D'+str(i),'=<<'+str(pilares[i-3].Label)+'>>.Width')

        tabela.set('E'+str(i),'=B'+str(i)+'*'+'C'+str(i)+'*''D'+str(i))
        tabela.setDisplayUnit('E'+str(i), 'm^3')

    equacao = '='
    for i in range(3,len(pilares)+3):
        equacao+='+E'+str(i)
    tabela.set('D'+str(len(pilares)+3),'Total:')
    tabela.set('E'+str(len(pilares)+3),equacao)
    tabela.setDisplayUnit('E'+str(len(pilares)+3), 'm^3')



if len(vigas) > 0:
    #TABELA VIGAS
    tabela = App.activeDocument().addObject('Spreadsheet::Sheet','Vigas')
    tabelas.append(tabela)
    #VIGAS############################################################
    tabela.mergeCells('A1:E1')#Uni as celulas da tabela
    tabela.setAlignment('A1:E1', 'center', 'keep')#Centraliza o texto
    tabela.set('A1','VIGAS')
    tabela.setBackground('A1',(0.000000,0.501961,0.000000))
    tabela.setForeground('A1', (1.000000,1.000000,1.000000))

    tabela.set('A2','Ref.')
    tabela.set('B2','Altura')
    tabela.set('C2','Comprimento')
    tabela.set('D2','Largura')
    tabela.set('E2','Volume')
    tabela.setBackground('A2:E2', (0.752941,0.752941,0.752941))

     
    for i in range(3,len(vigas)+3):
        tabela.set('A'+str(i),str(vigas[i-3].Label))
        tabela.set('B'+str(i),'=<<'+str(vigas[i-3].Label)+'>>.Height')
        tabela.set('C'+str(i),'=<<'+str(vigas[i-3].Label)+'>>.Length')
        tabela.set('D'+str(i),'=<<'+str(vigas[i-3].Label)+'>>.Width')

        tabela.set('E'+str(i),'=B'+str(i)+'*'+'C'+str(i)+'*''D'+str(i))
        tabela.setDisplayUnit('E'+str(i), 'm^3')

    equacao = '='
    for i in range(3,len(vigas)+3):
        equacao+='+E'+str(i)
    tabela.set('D'+str(len(vigas)+3),'Total:')
    tabela.set('E'+str(len(vigas)+3),equacao)
    tabela.setDisplayUnit('E'+str(len(vigas)+3), 'm^3')

if len(lajes) > 0:
    #TABELA VIGAS
    tabela = App.activeDocument().addObject('Spreadsheet::Sheet','Lajes')
    tabelas.append(tabela)
    #LAJES############################################################
    tabela.mergeCells('A1:D1')#Uni as celulas da tabela
    tabela.setAlignment('A1:D1', 'center', 'keep')#Centraliza o texto
    tabela.set('A1','Lajes')
    tabela.setBackground('A1',(0.000000,0.501961,0.000000))
    tabela.setForeground('A1', (1.000000,1.000000,1.000000))

    tabela.set('A2','Ref.')
    tabela.set('B2','Área')
    tabela.set('C2','Altura')
    tabela.set('D2','Volume')
    tabela.setBackground('A2:D2', (0.752941,0.752941,0.752941))

     
    for i in range(3,len(lajes)+3):
        tabela.set('A'+str(i),str(lajes[i-3].Label))
        tabela.set('B'+str(i),'=<<'+str(lajes[i-3].Label)+'>>.HorizontalArea')
        tabela.set('C'+str(i),'=<<'+str(lajes[i-3].Label)+'>>.Height')

        tabela.set('D'+str(i),'=B'+str(i)+'*'+'C'+str(i))
        tabela.setDisplayUnit('D'+str(i), 'm^3')

    equacao = '='
    equacao2 = '='
    for i in range(3,len(lajes)+3):
        equacao+='+B'+str(i)
        equacao2+= '+D'+str(i)

    tabela.set('A'+str(len(lajes)+3),'Total:')
    tabela.set('B'+str(len(lajes)+3),equacao)
    tabela.set('D'+str(len(lajes)+3),equacao2)
    tabela.setDisplayUnit('B'+str(len(lajes)+3), 'm^2')
    tabela.setDisplayUnit('D'+str(len(lajes)+3), 'm^3')


if len(paredes) > 0:
    #TABELA ALVENARIA
    tabela = App.activeDocument().addObject('Spreadsheet::Sheet','Alvenaria')
    tabelas.append(tabela)
    #LAJES############################################################
    tabela.mergeCells('A1:F1')#Uni as celulas da tabela
    tabela.setAlignment('A1:F1', 'center', 'keep')#Centraliza o texto
    tabela.set('A1','Alvenaria')
    tabela.setBackground('A1',(0.000000,0.501961,0.000000))
    tabela.setForeground('A1', (1.000000,1.000000,1.000000))

    tabela.set('A2','Ref.')
    tabela.set('B2','Comprimento')
    tabela.set('C2','Altura')
    tabela.set('D2','Largura')
    tabela.set('E2','Área')
    tabela.set('F2','Área lateral')
    tabela.setBackground('A2:F2', (0.752941,0.752941,0.752941))

     
    for i in range(3,len(paredes)+3):
        tabela.set('A'+str(i),str(paredes[i-3].Label))
        tabela.set('B'+str(i),'=<<'+str(paredes[i-3].Label)+'>>.Length')
        tabela.set('C'+str(i),'=<<'+str(paredes[i-3].Label)+'>>.Height')
        tabela.set('D'+str(i),'=<<'+str(paredes[i-3].Label)+'>>.Width')
        tabela.set('E'+str(i),'=<<'+str(paredes[i-3].Label)+'>>.Area')
        tabela.set('F'+str(i),'=<<'+str(paredes[i-3].Label)+'>>.VerticalArea')


    #######calculo dos totais#######
    equacao = '='
    equacao2 = '='
    for i in range(3,len(paredes)+3):
        equacao+='+E'+str(i)
        equacao2+= '+F'+str(i)

    tabela.set('D'+str(len(paredes)+3),'Total:')
    tabela.set('E'+str(len(paredes)+3),equacao)
    tabela.set('F'+str(len(paredes)+3),equacao2)
    tabela.setDisplayUnit('E'+str(len(paredes)+3), 'm^2')
    tabela.setDisplayUnit('F'+str(len(paredes)+3), 'm^2')



if len(janelas) > 0:
    #TABELA JANELAS
    tabela = App.activeDocument().addObject('Spreadsheet::Sheet','Janelas')
    tabelas.append(tabela)
    #LAJES############################################################
    tabela.mergeCells('A1:C1')#Uni as celulas da tabela
    tabela.setAlignment('A1:C1', 'center', 'keep')#Centraliza o texto
    tabela.set('A1','Janelas')
    tabela.setBackground('A1',(0.000000,0.501961,0.000000))
    tabela.setForeground('A1', (1.000000,1.000000,1.000000))

    tabela.set('A2','Tipo')
    tabela.set('B2','Qaunt.')
    tabela.set('C2','Descrição')
    tabela.setBackground('A2:C2', (0.752941,0.752941,0.752941))

    ######### conta as janelas ###########
    tipos = []
    for i in janelas:
        cont = 0
        for j in tipos:
            if str(i.Tag) == j[0]:
                j[1] += 1
                cont += 1
        if cont == 0:
            tipos.append([str(i.Tag),1, str(i.Description)])


     
    for i in range(3,len(tipos)+3):
        tabela.set('A'+str(i),str(tipos[i-3][0]))
        tabela.set('B'+str(i),str(tipos[i-3][1]))
        tabela.set('C'+str(i),str(tipos[i-3][2]))
        


    #######calculo dos totais#######
    equacao = '='
    for i in range(3,len(tipos)+3):
        equacao+='+B'+str(i)

    tabela.set('A'+str(len(tipos)+3),'Total:')
    tabela.set('B'+str(len(tipos)+3),equacao)



if len(portas) > 0:
    #TABELA PORTAS
    tabela = App.activeDocument().addObject('Spreadsheet::Sheet','Portas')
    tabelas.append(tabela)
    #LAJES############################################################
    tabela.mergeCells('A1:C1')#Uni as celulas da tabela
    tabela.setAlignment('A1:C1', 'center', 'keep')#Centraliza o texto
    tabela.set('A1','Portas')
    tabela.setBackground('A1',(0.000000,0.501961,0.000000))
    tabela.setForeground('A1', (1.000000,1.000000,1.000000))

    tabela.set('A2','Tipo')
    tabela.set('B2','Qaunt.')
    tabela.set('C2','Descrição')
    tabela.setBackground('A2:C2', (0.752941,0.752941,0.752941))

    ######### conta as portas ###########
    tipos = []
    for i in portas:
        cont = 0
        for j in tipos:
            if str(i.Tag) == j[0]:
                j[1] += 1
                cont += 1
        if cont == 0:
            tipos.append([str(i.Tag),1, str(i.Description)])


     
    for i in range(3,len(tipos)+3):
        tabela.set('A'+str(i),str(tipos[i-3][0]))
        tabela.set('B'+str(i),str(tipos[i-3][1]))
        tabela.set('C'+str(i),str(tipos[i-3][2]))
        


    #######calculo dos totais#######
    equacao = '='
    for i in range(3,len(tipos)+3):
        equacao+='+B'+str(i)

    tabela.set('A'+str(len(tipos)+3),'Total:')
    tabela.set('B'+str(len(tipos)+3),equacao)


################  Agrupar tabelas#####################
grupo = App.ActiveDocument.addObject("App::DocumentObjectGroup","Quantitativo")
for i in tabelas:
    print(i)
    i.adjustRelativeLinks(grupo)
    grupo.addObject(i)

App.ActiveDocument.recompute()
